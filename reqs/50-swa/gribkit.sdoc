[DOCUMENT]
TITLE: Softwarearchitektur gribkit (SWA)
PREFIX: SWA-GRIB-

[GRAMMAR]
IMPORT_FROM_FILE: @architektur

[TEXT]
STATEMENT: >>>
Softwarearchitektur nach ISO/IEC/IEEE 12207 für das Softwareelement SYSA-SW-GRIBKIT. Jede
Komponente entspricht einem Modul unter ``packages/gribkit/src/gribkit``. gribkit hat keine
Abhängigkeit zu anderen Paketen von PredictionDB.
<<<

[[SECTION]]
TITLE: Komponenten

[ELEMENT]
UID: SWA-GRIB-IDX
ART: Komponente
STATUS: Umgesetzt
TITLE: Inventar und Byte-Bereiche
STATEMENT: >>>
Parser für ``.idx``, Auswahl, fehlende Spezifikationen, Byte-Bereiche.
<<<
ORT: packages/gribkit/src/gribkit/idx.py
RELATIONS:
- TYPE: Parent
  VALUE: SWR-GRIB-001
- TYPE: Parent
  VALUE: SWR-GRIB-002
- TYPE: Parent
  VALUE: SWR-GRIB-003
- TYPE: Parent
  VALUE: SWR-GRIB-008

[ELEMENT]
UID: SWA-GRIB-HEADERS
ART: Komponente
STATUS: Umgesetzt
TITLE: Inventar aus Köpfen
STATEMENT: >>>
Nachrichtenköpfe lesen, Grenzen finden, Zeilen wie wgrib2.
<<<
ORT: packages/gribkit/src/gribkit/headers.py
RELATIONS:
- TYPE: Parent
  VALUE: SWR-GRIB-004
- TYPE: Parent
  VALUE: SWR-GRIB-008

[ELEMENT]
UID: SWA-GRIB-GRIB
ART: Komponente
STATUS: Umgesetzt
TITLE: Trennen und Zuschneiden
STATEMENT: >>>
Nachrichten trennen, beschreiben, zuschneiden und neu packen.
<<<
ORT: packages/gribkit/src/gribkit/grib.py
RELATIONS:
- TYPE: Parent
  VALUE: SWR-GRIB-005
- TYPE: Parent
  VALUE: SWR-GRIB-006
- TYPE: Parent
  VALUE: SWR-GRIB-007

[ELEMENT]
UID: SWA-GRIB-BBOX
ART: Komponente
STATUS: Umgesetzt
TITLE: Ausschnitt
STATEMENT: >>>
Geografischer Ausschnitt mit Prüfung.
<<<
ORT: packages/gribkit/src/gribkit/bbox.py
RELATIONS:
- TYPE: Parent
  VALUE: SWR-GRIB-006

[ELEMENT]
UID: SWA-GRIB-TESTING
ART: Komponente
STATUS: Umgesetzt
TITLE: Testhilfen
STATEMENT: >>>
Synthetische GRIB2-Nachrichten mit bekannten Werten. Nur für Tests.
<<<
ORT: packages/gribkit/src/gribkit/testing.py

[[/SECTION]]

[[SECTION]]
TITLE: Schnittstellen

[ELEMENT]
UID: SWA-GRIB-IF-API
ART: Schnittstelle
STATUS: Umgesetzt
TITLE: Python-API
STATEMENT: >>>
gribkit → wx-ingest, wx-exchange, pdb-predict. ``parse_idx``, ``select``, ``merge_ranges``, ``parse_head``, ``iter_messages``, ``crop``, ``BBox``.
<<<
RELATIONS:
- TYPE: Parent
  VALUE: SWR-GRIB-001
- TYPE: Parent
  VALUE: SWR-GRIB-003
- TYPE: Parent
  VALUE: SWR-GRIB-004
- TYPE: Parent
  VALUE: SWR-GRIB-006

[[/SECTION]]

[DOCUMENT]
TITLE: Softwareanforderungen wx-exchange (SRS)
PREFIX: SWR-WXX-

[GRAMMAR]
IMPORT_FROM_FILE: @anforderung

[TEXT]
STATEMENT: >>>
Software Requirements Specification nach ISO/IEC/IEEE 29148 für das Softwareelement
SYSA-SW-WXX (``services/wx_exchange``): Silber-Austausch über GHCR für GFS und GEFS, vollständige
``.idx`` zu GDEX, GEFS-Dienst der VM und der öffentliche Grafana-Snapshot.
<<<

[[SECTION]]
TITLE: Registry und Artefakte

[REQUIREMENT]
UID: SWR-WXX-001
ART: Schnittstelle
STATUS: Umgesetzt
NACHWEIS: Test
TITLE: OCI-Registry
STATEMENT: >>>
wx-exchange muss Tags, Manifeste und Blobs einer OCI-Registry über die Distribution API lesen
und schreiben, ohne ``oras`` oder Docker. Lesen muss anonym gehen, Schreiben mit
``WX_EXCHANGE_USERNAME``/``WX_EXCHANGE_TOKEN``. Vorhandene Blobs werden nicht erneut
hochgeladen, Serverfehler und Verbindungsabbrüche bis zu dreimal wiederholt. Jede Quelle hat ihr
eigenes Repository.
<<<
QUELLE: ARCHITEKTUR.md 5.5.3
RELATIONS:
- TYPE: Parent
  VALUE: SYSR-PUB-001

[REQUIREMENT]
UID: SWR-WXX-002
ART: Schnittstelle
STATUS: Umgesetzt
NACHWEIS: Test
TITLE: GFS-Silber-Artefakt
STATEMENT: >>>
wx-exchange muss je Monat und Laufzeit ein Manifest mit Tag ``JJJJ-MM-HHz`` und je Lauf einen
Layer (Tar des Zarr-Stores) schreiben. Jeder Layer trägt Lauf, Fingerabdruck der Eingaben,
Inhalts-Hash, ``SILVER_VERSION`` und Schrittzahl; das Manifest Lizenz, Quellenvermerk und die im
Archiv fehlenden Läufe.
<<<
RELATIONS:
- TYPE: Parent
  VALUE: SYSR-PUB-001
- TYPE: Parent
  VALUE: SYSR-QA-004

[REQUIREMENT]
UID: SWR-WXX-003
ART: Qualität
STATUS: Umgesetzt
NACHWEIS: Test
TITLE: Reproduzierbare Layer
STATEMENT: >>>
Dasselbe Silber muss byte-gleiche Tars ergeben. Der Inhalts-Hash darf den Zeitpunkt des
Bronze-Abschlusses nicht enthalten, damit ein Neubau ohne inhaltliche Änderung nichts hochlädt.
<<<
RELATIONS:
- TYPE: Parent
  VALUE: SYSR-PUB-001

[[/SECTION]]

[[SECTION]]
TITLE: GFS-Historie im Runner

[REQUIREMENT]
UID: SWR-WXX-010
ART: Funktional
STATUS: Umgesetzt
NACHWEIS: Test
TITLE: Plan nur für Lücken
STATEMENT: >>>
``gfs plan`` muss aus den Manifesten in GHCR die Monate und Laufzeiten ermitteln, in denen Läufe
ohne passenden Fingerabdruck fehlen, in Blöcken von Jahren vom jüngsten Monat rückwärts und mit
den Laufzeiten in der angegebenen Reihenfolge, und daraus die Matrix für GitHub Actions ausgeben.
<<<
RELATIONS:
- TYPE: Parent
  VALUE: SYSR-PUB-002

[REQUIREMENT]
UID: SWR-WXX-011
ART: Funktional
STATUS: Umgesetzt
NACHWEIS: Test
TITLE: Monat veröffentlichen
STATEMENT: >>>
``gfs publish`` muss in einem Monat und einer Laufzeit die fehlenden Läufe aus dem Archiv laden,
Bronze und Silber nur im Arbeitsverzeichnis bauen, einen Lauf nur hochladen, wenn er neu ist oder
sein Inhalts-Hash sich geändert hat, im Archiv fehlende Läufe vermerken und das Manifest nach
jedem Lauf schreiben. Mit ``--rebuild`` wird jeder Lauf neu gebaut.
<<<
RELATIONS:
- TYPE: Parent
  VALUE: SYSR-PUB-002
- TYPE: Parent
  VALUE: SYSR-WX-005

[REQUIREMENT]
UID: SWR-WXX-012
ART: Funktional
STATUS: Umgesetzt
NACHWEIS: Demonstration
TITLE: Vorlagen für Archive ohne .idx
STATEMENT: >>>
``gfs templates`` muss die Kopf-Inventare für ``header_scan`` an je einem Lauf pro Monat prüfen,
fehlende Schritte und neue Varianten ergänzen und die Vorlagendatei neu schreiben.
<<<
QUELLE: Workflow gfs-templates.yml
RELATIONS:
- TYPE: Parent
  VALUE: SYSR-WX-005

[[/SECTION]]

[[SECTION]]
TITLE: Import und Prüfung auf der VM

[REQUIREMENT]
UID: SWR-WXX-020
ART: Funktional
STATUS: Umgesetzt
NACHWEIS: Test
TITLE: Silber importieren
STATEMENT: >>>
``gfs import`` muss alle Läufe im Zeitraum, die lokal nicht als vollständiges Silber der aktuellen
``SILVER_VERSION`` vorliegen, aus GHCR nach ``wx-silver`` holen, mehrere parallel und in der
Reihenfolge der Laufzeiten. Selbst gebautes Silber bleibt unangetastet.
<<<
RELATIONS:
- TYPE: Parent
  VALUE: SYSR-PUB-001
- TYPE: Parent
  VALUE: SYSR-WX-005

[REQUIREMENT]
UID: SWR-WXX-021
ART: Schnittstelle
STATUS: Umgesetzt
NACHWEIS: Test
TITLE: Bestand melden
STATEMENT: >>>
Der Import muss zu holende Läufe zu Beginn als ``loading`` und jeden geholten als ``present`` in
``meta.silver_run`` melden.
<<<
RELATIONS:
- TYPE: Parent
  VALUE: SYSR-OPS-003

[REQUIREMENT]
UID: SWR-WXX-022
ART: Funktional
STATUS: Umgesetzt
NACHWEIS: Test
TITLE: Eigenes Silber gegen GHCR prüfen
STATEMENT: >>>
``gfs verify`` muss je Lauf das lokal gebaute Silber über den Inhalts-Hash mit GHCR vergleichen
und ``equal``, ``different`` (mit den abweichenden Dateien), ``imported`` oder ``local_missing``
melden. Ein Layer wird nur bei Abweichung geladen.
<<<
RELATIONS:
- TYPE: Parent
  VALUE: SYSR-PUB-001

[[/SECTION]]

[[SECTION]]
TITLE: Vollständige .idx zu GDEX

[REQUIREMENT]
UID: SWR-WXX-030
ART: Funktional
STATUS: Umgesetzt
NACHWEIS: Test
TITLE: Index-Layer bauen
STATEMENT: >>>
``gfs idx-build`` muss je GRIB-Datei eines Monats und einer Laufzeit eine vollständige ``.idx``
im Format von ``wgrib2 -s`` aus den Nachrichtenköpfen bauen und als Layer mit dem Stand
``complete``, ``failed``, ``absent``, ``broken`` und ``unknown`` ablegen. Fehlgeschlagene Dateien
werden im selben Job wiederholt, im Archiv kaputte nicht. Die Arbeit lässt sich auf
mehrere Prozesse verteilen.
<<<
QUELLE: Workflow gfs-idx.yml
RELATIONS:
- TYPE: Parent
  VALUE: SYSR-WX-005
- TYPE: Parent
  VALUE: SYSR-PUB-002

[REQUIREMENT]
UID: SWR-WXX-031
ART: Funktional
STATUS: Umgesetzt
NACHWEIS: Test
TITLE: Index-Artefakt fortsetzen
STATEMENT: >>>
Ein erneuter Start muss nur Monate ohne vollständigen Layer bearbeiten und schon gebaute ``.idx``
übernehmen. ``idx-manifest`` muss das Manifest auch schreiben, wenn einzelne Jobs scheitern, und
dabei Layer ohne Blob auslassen.
<<<
RELATIONS:
- TYPE: Parent
  VALUE: SYSR-WX-005

[REQUIREMENT]
UID: SWR-WXX-032
ART: Funktional
STATUS: Umgesetzt
NACHWEIS: Test
TITLE: Index statt Köpfe lesen
STATEMENT: >>>
Liegt für einen Monat ein Index-Layer vor, muss ``publish`` die gewählten Nachrichten über die
``.idx`` per Byte-Bereich lesen. Passt eine ``.idx`` nicht zur Datei, fällt es auf Vorlagen und
Köpfe zurück.
<<<
RELATIONS:
- TYPE: Parent
  VALUE: SYSR-WX-002
- TYPE: Parent
  VALUE: SYSR-WX-005

[[/SECTION]]

[[SECTION]]
TITLE: GEFS-Ensemble

[REQUIREMENT]
UID: SWR-WXX-040
ART: Schnittstelle
STATUS: Umgesetzt
NACHWEIS: Test
TITLE: GEFS-Konfiguration
STATEMENT: >>>
wx-exchange muss Mitglieder, Laufzeiten, Schritte, Felder, Ausschnitt und Archiv-URLs des GEFS aus
``config/sources/gefs_0p5.yaml`` lesen.
<<<
RELATIONS:
- TYPE: Parent
  VALUE: SYSR-WX-007
- TYPE: Parent
  VALUE: SYSR-QA-003

[REQUIREMENT]
UID: SWR-WXX-041
ART: Funktional
STATUS: Umgesetzt
NACHWEIS: Test
TITLE: GEFS-Felder per Byte-Bereich
STATEMENT: >>>
wx-exchange muss je Mitglied und Schritt aus der ``.idx`` nur die konfigurierten Felder wählen,
benachbarte Nachrichten zu Byte-Bereichen zusammenfassen und laden.
<<<
RELATIONS:
- TYPE: Parent
  VALUE: SYSR-WX-007
- TYPE: Parent
  VALUE: SYSR-WX-002

[REQUIREMENT]
UID: SWR-WXX-042
ART: Funktional
STATUS: Umgesetzt
NACHWEIS: Test
TITLE: GEFS je Region und Mitglied verdichten
STATEMENT: >>>
wx-exchange muss jeden GEFS-Lauf je Region, Mitglied, Größe und Schritt mit den Gewichten der
Regionsdatei verdichten. Blockierende Arbeit darf den Standard-Executor nicht belegen.
<<<
QUELLE: ARCHITEKTUR.md 5.6
RELATIONS:
- TYPE: Parent
  VALUE: SYSR-WX-007

[REQUIREMENT]
UID: SWR-WXX-043
ART: Schnittstelle
STATUS: Umgesetzt
NACHWEIS: Test
TITLE: GEFS-Artefakt
STATEMENT: >>>
``gefs publish`` muss je Monat ein Manifest ``JJJJ-MM-00z`` mit einem reproduzierbaren Layer je Lauf
schreiben, nur neue oder geänderte Läufe hochladen und fehlende vermerken. Der Fingerabdruck
ändert sich mit Konfiguration und Regionen.
<<<
RELATIONS:
- TYPE: Parent
  VALUE: SYSR-PUB-002
- TYPE: Parent
  VALUE: SYSR-WX-007

[REQUIREMENT]
UID: SWR-WXX-044
ART: Funktional
STATUS: Umgesetzt
NACHWEIS: Test
TITLE: Regionen bauen
STATEMENT: >>>
``gefs regions`` muss die Regionen (Gebotszonen aus Natural Earth, Technologie-Gewichte aus
MaStR-Zellen) auf dem 0,5°-Gitter berechnen und als versionierte Datei schreiben.
<<<
RELATIONS:
- TYPE: Parent
  VALUE: SYSR-WX-007
- TYPE: Parent
  VALUE: SYSR-WX-008

[REQUIREMENT]
UID: SWR-WXX-045
ART: Funktional
STATUS: Umgesetzt
NACHWEIS: Test
TITLE: GEFS live auf der VM
STATEMENT: >>>
``gefs vm --live`` muss die Läufe des aktuellen Monats und der letzten Tage des Vormonats bauen, sobald
der letzte Schritt des letzten Mitglieds im Archiv liegt, die zugeschnittenen Nachrichten in
``wx-bronze`` und das Silber in ``wx-silver`` und GHCR ablegen.
<<<
RELATIONS:
- TYPE: Parent
  VALUE: SYSR-WX-007

[REQUIREMENT]
UID: SWR-WXX-046
ART: Funktional
STATUS: Umgesetzt
NACHWEIS: Test
TITLE: GEFS-Historie importieren
STATEMENT: >>>
``gefs vm`` muss abgeschlossene Monate aus GHCR in Portionen importieren, nur Layer mit aktuellem
Fingerabdruck, und lokal vorhandene Läufe im Bestand nachtragen.
<<<
RELATIONS:
- TYPE: Parent
  VALUE: SYSR-WX-007
- TYPE: Parent
  VALUE: SYSR-PUB-001

[REQUIREMENT]
UID: SWR-WXX-047
ART: Funktional
STATUS: Umgesetzt
NACHWEIS: Test
TITLE: GEFS-Gold
STATEMENT: >>>
``gefs vm`` muss je Lauf Mittel, Streuung, P10 und P90 über die Mitglieder je Region, Größe und
Schritt nach ``feat.nwp_value`` schreiben (Aggregation ``ensemble``), jüngste Läufe zuerst. Live,
Import und Gold dürfen sich nicht gegenseitig aufhalten; ein Rückstand wird abgearbeitet.
<<<
RELATIONS:
- TYPE: Parent
  VALUE: SYSR-WX-007
- TYPE: Parent
  VALUE: SYSR-PR-002

[REQUIREMENT]
UID: SWR-WXX-048
ART: Funktional
STATUS: Umgesetzt
NACHWEIS: Test
TITLE: GEFS-Bronze aufräumen
STATEMENT: >>>
Bronze eines GEFS-Laufs darf ``gefs vm`` erst nach ``--bronze-days`` löschen und nur, wenn das
Silber lokal und in GHCR denselben Inhalts-Hash hat.
<<<
RELATIONS:
- TYPE: Parent
  VALUE: SYSR-QA-001

[REQUIREMENT]
UID: SWR-WXX-049
ART: Funktional
STATUS: Umgesetzt
NACHWEIS: Test
TITLE: GEFS live in GitHub Actions
STATEMENT: >>>
Den aktuellen Monat muss täglich der Workflow ``gefs-live.yml`` nach dem 00Z-Lauf als Silber nach
GHCR bauen (mit den letzten Tagen des Vormonats). ``gefs vm --no-live`` lädt dann kein Bronze
mehr, sondern importiert auch den aktuellen Monat aus GHCR und rechnet daraus Gold.
<<<
RELATIONS:
- TYPE: Parent
  VALUE: SYSR-WX-007

[[/SECTION]]

[[SECTION]]
TITLE: Öffentlicher Snapshot

[REQUIREMENT]
UID: SWR-WXX-050
ART: Funktional
STATUS: Umgesetzt
NACHWEIS: Test
TITLE: Wochenprognose als Snapshot
STATEMENT: >>>
``snapshot`` muss täglich zur eingestellten Uhrzeit das Dashboard „Prognose öffentlich“ holen, die
Abfragen der Prognosepanels für heute 00:00 bis Ende D+15 (auch über die Zeitumstellung) ausführen,
die Ergebnisse einbetten, den Snapshot extern mit Ablaufzeit hochladen und die früheren, noch
gültigen Stände verlinken.
<<<
QUELLE: Projektentscheidung Prognose öffentlich
RELATIONS:
- TYPE: Parent
  VALUE: SYSR-PUB-006

[REQUIREMENT]
UID: SWR-WXX-051
ART: Funktional
STATUS: Umgesetzt
NACHWEIS: Test
TITLE: Fester Kurzlink
STATEMENT: >>>
Nach dem Hochladen muss ``snapshot`` einen Kurzlink (Short.io oder Shlink) auf den neuen Snapshot
umbiegen und ihn bei Short.io anlegen, wenn er fehlt. Ohne Kurzlink wird nur hochgeladen.
<<<
RELATIONS:
- TYPE: Parent
  VALUE: SYSR-PUB-006

[REQUIREMENT]
UID: SWR-WXX-052
ART: Funktional
STATUS: Umgesetzt
NACHWEIS: Test
TITLE: Vorlauf-Panels für morgen im Snapshot
STATEMENT: >>>
Der Snapshot muss die Panels „Morgen“ (Preis und Last mit D+1 bis D+15, je Champion und
Challenger, mit Day-Ahead-Preis bzw. ÜNB-Lastprognose) für den Liefertag nach dem Stand von 0 bis
24 Uhr Ortszeit enthalten, mit der Uhrzeit als x-Achse, auch an Tagen der Zeitumstellung.
<<<
QUELLE: Nutzerwunsch 2026-11-01
RELATIONS:
- TYPE: Parent
  VALUE: SYSR-OPS-003

[[/SECTION]]

[[SECTION]]
TITLE: Gold und Gewichte im Runner

[REQUIREMENT]
UID: SWR-WXX-070
ART: Schnittstelle
STATUS: Umgesetzt
NACHWEIS: Test
TITLE: Gewichte-Artefakt
STATEMENT: >>>
wx-exchange muss die Gewichte einer Clusterung als OCI-Artefakt
``predictiondb-data/gfs-0p25-weights`` mit den Tags ``<Version>``, ``<Version>-<MaStR-Export>``
und ``latest`` schreiben können: Anteil je Gitterzelle und Region samt Nabenhöhe
(``clusters.parquet``), Bestand je Cluster nur an den Tagen seiner Änderung
(``capacity.parquet``) und den Stand der Clusterung (``cells.parquet``). Feste Regionen aus dem
Repo (Zonen, Standorte) ergeben dieselbe Form ohne Bestand.
<<<
QUELLE: ARCHITEKTUR.md 5.5.7
RELATIONS:
- TYPE: Parent
  VALUE: SYSR-PUB-002
- TYPE: Parent
  VALUE: SYSR-EN-004

[REQUIREMENT]
UID: SWR-WXX-071
ART: Schnittstelle
STATUS: Umgesetzt
NACHWEIS: Test
TITLE: Gold-Artefakt
STATEMENT: >>>
wx-exchange muss je Monat und Laufzeit ein Manifest mit Tag ``<Version>-JJJJ-MM-HHz`` schreiben,
mit einem Layer ``gold.parquet`` (``run_time, valid_time, region, feature, value``, sortiert nach
Feature, Region, Lauf und Zeit) und den Gewichten, mit denen gerechnet wurde. Das Manifest trägt
Lizenz, Quellenvermerk, die enthaltenen und fehlenden Läufe und einen Fingerabdruck aus
``FEATURES_VERSION``, Feature-Konfiguration, Gewichten und den Inhalts-Hashes des Silbers.
<<<
QUELLE: ARCHITEKTUR.md 5.5.7
RELATIONS:
- TYPE: Parent
  VALUE: SYSR-PUB-002
- TYPE: Parent
  VALUE: SYSR-QA-004

[REQUIREMENT]
UID: SWR-WXX-072
ART: Funktional
STATUS: Umgesetzt
NACHWEIS: Test
TITLE: Gold ohne Datenbank rechnen
STATEMENT: >>>
``gold build`` muss Gold eines Monats und einer Laufzeit nur aus dem Silber in GHCR und dem
Gewichte-Artefakt bzw. den festen Regionen rechnen, mit denselben Features wie ``wx-process``,
und es nur schreiben, wenn sich der Fingerabdruck geändert hat (``--rebuild``: immer).
<<<
RELATIONS:
- TYPE: Parent
  VALUE: SYSR-PUB-002

[REQUIREMENT]
UID: SWR-WXX-073
ART: Funktional
STATUS: Umgesetzt
NACHWEIS: Test
TITLE: Plan für veraltetes Gold
STATEMENT: >>>
``gold plan`` muss die Monate und Laufzeiten mit Silber im Zeitraum ausgeben, deren Gold fehlt
oder einen anderen Fingerabdruck trägt, in der Reihenfolge der Laufzeiten und darin die jüngsten
Monate zuerst, aufgeteilt in Matrix-Blöcke für GitHub Actions.
<<<
RELATIONS:
- TYPE: Parent
  VALUE: SYSR-PUB-002

[REQUIREMENT]
UID: SWR-WXX-074
ART: Funktional
STATUS: Umgesetzt
NACHWEIS: Test
TITLE: Neuer MaStR-Stand fällig
STATEMENT: >>>
``gold weights-due`` muss neue Gewichte als fällig melden, wenn es noch keine gibt oder ihr
MaStR-Export vor dem laufenden Quartal liegt.
<<<
RELATIONS:
- TYPE: Parent
  VALUE: SYSR-EN-004

[REQUIREMENT]
UID: SWR-WXX-075
ART: Funktional
STATUS: Umgesetzt
NACHWEIS: Test
TITLE: Clusterung im Runner fortschreiben
STATEMENT: >>>
``gold weights-build`` muss den MaStR-Export in eine leere Datenbank importieren und vorher die
Clusterung des letzten Gewichte-Artefakts wiederherstellen, damit ``mastr-ingest`` sie wie auf
der VM fortschreibt und erst nach ``recluster_after_days`` neu clustert.
<<<
RELATIONS:
- TYPE: Parent
  VALUE: SYSR-EN-004

[[/SECTION]]

[[SECTION]]
TITLE: Energiedaten im Runner

[REQUIREMENT]
UID: SWR-WXX-080
ART: Schnittstelle
STATUS: Umgesetzt
NACHWEIS: Test
TITLE: Energie-Artefakt je Jahr
STATEMENT: >>>
``energy build JJJJ`` muss alle Datensätze der freien Quellen für das Kalenderjahr (Ortszeit
Berlin) ohne Datenbank abrufen und als OCI-Artefakt ``predictiondb-data/energy:JJJJ`` ablegen:
ein Parquet je Quelle mit ``code``, ``ts``, ``value`` und ``published`` (wie
``energy.value``) und ``sources.json`` mit Rang, Lizenzklasse, Lizenz und Reihen je Quelle. Die
eigenen Marktwerte werden wie auf der VM aus Preis und Erzeugung gerechnet. Unfreie Quellen
und solche der Klasse „nur Training“ dürfen nicht ins Artefakt.
<<<
QUELLE: Nutzerwunsch 2026-11-12, ARCHITEKTUR.md 5.5.8
RELATIONS:
- TYPE: Parent
  VALUE: SYSR-EN-001
- TYPE: Parent
  VALUE: SYSR-PUB-002

[REQUIREMENT]
UID: SWR-WXX-081
ART: Funktional
STATUS: Umgesetzt
NACHWEIS: Test
TITLE: Beste Quelle je Reihe
STATEMENT: >>>
Aus den Energie-Artefakten muss sich je Reihe und Zeitpunkt der Wert der Quelle mit dem
kleinsten Rang ergeben, wie in der Sicht ``energy.value_best``.
<<<
RELATIONS:
- TYPE: Parent
  VALUE: SYSR-EN-001

[REQUIREMENT]
UID: SWR-WXX-082
ART: Funktional
STATUS: Umgesetzt
NACHWEIS: Test
TITLE: Jahre planen, Ausfälle überbrücken
STATEMENT: >>>
``energy plan`` muss fehlende Jahre, Jahre mit anderer Formatversion oder veralteten Quellen,
das laufende Jahr und bis Ende Februar das Vorjahr auswählen. Scheitert beim Bau ein Datensatz,
müssen die bisherigen Werte dieser Quelle im Artefakt bleiben (Annotation ``stale``); ohne
bisherige Werte wird nichts veröffentlicht. Unveränderte Jahre bekommen kein neues Manifest.
<<<
RELATIONS:
- TYPE: Parent
  VALUE: SYSR-PUB-002

[REQUIREMENT]
UID: SWR-WXX-083
ART: Qualität
STATUS: Umgesetzt
NACHWEIS: Test
TITLE: Laufendes Jahr nur im Rückblick abrufen
STATEMENT: >>>
Im laufenden Jahr muss ``energy build`` Datensätze mit Blöcken bis 31 Tage nur für die letzten
62 Tage neu abrufen und mit den bisherigen Werten zusammenführen; ganze Dateien kommen
vollständig, ``--full`` ruft alles ab. Quellen, die ein Lauf nicht abruft, bleiben unverändert
im Artefakt.
<<<
RELATIONS:
- TYPE: Parent
  VALUE: SYSR-PUB-002

[[/SECTION]]

[[SECTION]]
TITLE: Robustheit

[REQUIREMENT]
UID: SWR-WXX-060
ART: Qualität
STATUS: Umgesetzt
NACHWEIS: Test
TITLE: Artefakte fremder Instanzen prüfen
STATEMENT: >>>
Manifeste und Layer aus GHCR müssen vor der Übernahme geprüft werden: Tar-Einträge nur mit
relativen Pfaden ohne ``..``, eindeutig, mit Obergrenzen für Anzahl und entpackte Größe;
Digests nur als ``sha256:<64 hex>``; Tags nur in der Form von ``tag``; Annotationen, Layer und
``zarr.json`` mit den erwarteten Typen. Ungültiges muss als ``ArtifactError`` gemeldet werden,
der Import überspringt das betroffene Manifest. Nachgewiesen wird das mit Property-Tests
(Hypothesis) in jeder CI und regelmäßig mit dem Fuzzer ``fuzz/predictiondb_fuzz.py`` (Atheris).
<<<
RATIONALE: >>>
Bis 2026-11-01 übernahm ``files_from_tar`` jeden Namen ungeprüft und ohne Größengrenze, und ein
unvollständiger Deskriptor brach den Import mit ``KeyError`` ab.
<<<
RELATIONS:
- TYPE: Parent
  VALUE: SYSR-SEC-009

[[/SECTION]]

[DOCUMENT]
TITLE: Systemanforderungen (SyRS)
PREFIX: SYSR-

[GRAMMAR]
IMPORT_FROM_FILE: @anforderung

[TEXT]
STATEMENT: >>>
System Requirements Specification nach ISO/IEC/IEEE 29148. „System“ ist PredictionDB mit allem,
was zum Betrieb gehört: der Stack auf der VM, Garage, PostgreSQL, Grafana, die Workflows in GitHub
Actions und die Ablage in GHCR. Externe Quellen sind Umgebung. Wie das System gegliedert ist,
steht in der Systemarchitektur (SYSA), die Begründungen in docs/ARCHITEKTUR.md.

Jede Systemanforderung leitet sich aus mindestens einer Stakeholder-Anforderung ab (``Parent``)
und nennt die vorgesehene Nachweisart. Systemtests gegen diese Ebene gibt es bisher kaum; der
Nachweis läuft heute über Integrationstests, Backtests, Dashboards und Inspektion.
<<<

[[SECTION]]
TITLE: Wetterdaten

[REQUIREMENT]
UID: SYSR-WX-001
ART: Funktional
STATUS: Umgesetzt
NACHWEIS: Test, Demonstration
TITLE: GFS-Läufe laufend laden
STATEMENT: >>>
Das System muss jeden GFS-0,25°-Lauf (00, 06, 12, 18Z, 384 h) für den Ausschnitt 44–58° N,
0–20° E laden. Ein veröffentlichter Prognoseschritt muss spätestens 10 min nach seiner
Veröffentlichung erkannt und geladen werden.
<<<
QUELLE: SPECIFICATION.md 6.1; ARCHITEKTUR.md 3.1, 4
RELATIONS:
- TYPE: Parent
  VALUE: STK-001
- TYPE: Parent
  VALUE: STK-002
- TYPE: Parent
  VALUE: STK-010

[REQUIREMENT]
UID: SYSR-WX-002
ART: Qualität
STATUS: Umgesetzt
NACHWEIS: Test, Analyse
TITLE: Nur benötigte Daten übertragen
STATEMENT: >>>
Das System muss nur die konfigurierten Variablen und den Ausschnitt übertragen, über
serverseitige Filter oder Byte-Bereiche, und die Nutzungsgrenzen jedes Endpunkts einhalten.
<<<
QUELLE: ARCHITEKTUR.md 4.1
RELATIONS:
- TYPE: Parent
  VALUE: STK-038
- TYPE: Parent
  VALUE: STK-006

[REQUIREMENT]
UID: SYSR-WX-003
ART: Qualität
STATUS: Umgesetzt
NACHWEIS: Test
TITLE: Redundante Wetterendpunkte
STATEMENT: >>>
Fällt ein Endpunkt aus oder fehlt dort ein Schritt, muss das System den nächsten Endpunkt in der
konfigurierten Rangfolge versuchen.
<<<
QUELLE: SPECIFICATION.md 6.1; ARCHITEKTUR.md 3.3
RELATIONS:
- TYPE: Parent
  VALUE: STK-004
- TYPE: Parent
  VALUE: STK-017

[REQUIREMENT]
UID: SYSR-WX-004
ART: Funktional
STATUS: Umgesetzt
NACHWEIS: Test
TITLE: Original unverändert und geprüft ablegen
STATEMENT: >>>
Das System muss jeden geladenen Schritt verlustfrei als GRIB2 (Bronze) ablegen, mit Herkunft,
Prüfsumme und fehlenden Variablen. Ein Lauf gilt erst als vollständig, wenn alle Schritte liegen.
<<<
QUELLE: SPECIFICATION.md 3.1, 6.1; ARCHITEKTUR.md 4.2, 5.1
RELATIONS:
- TYPE: Parent
  VALUE: STK-018
- TYPE: Parent
  VALUE: STK-015

[REQUIREMENT]
UID: SYSR-WX-005
ART: Funktional
STATUS: Umgesetzt
NACHWEIS: Test
TITLE: Historie nachladen
STATEMENT: >>>
Das System muss vergangene GFS-Läufe ab 2021-03-22 12Z (GFS v16) aus Archiv-Endpunkten
nachladen können. Ein abgebrochener Backfill muss mit demselben Aufruf fortgesetzt werden können.
<<<
QUELLE: services/wx_ingest/README.md; Projektentscheidung 2026-10-29
RELATIONS:
- TYPE: Parent
  VALUE: STK-015

[REQUIREMENT]
UID: SYSR-WX-006
ART: Funktional
STATUS: Umgesetzt
NACHWEIS: Test
TITLE: Wetter platzsparend aufbereiten
STATEMENT: >>>
Das System muss jeden vollständigen Lauf in ein kompaktes Gitterformat (Silber) überführen und
daraus Wetter-Features je Gebietscluster (Gold) berechnen. Wetterwerte dürfen nicht zeilenweise
je Gitterpunkt in der Datenbank liegen.
<<<
QUELLE: SPECIFICATION.md 7; ARCHITEKTUR.md 5.1, 5.4
RELATIONS:
- TYPE: Parent
  VALUE: STK-006
- TYPE: Parent
  VALUE: STK-010

[REQUIREMENT]
UID: SYSR-WX-007
ART: Funktional
STATUS: Umgesetzt
NACHWEIS: Demonstration
TITLE: Ensemble für längere Horizonte
STATEMENT: >>>
Das System muss das GEFS-Ensemble bis D+16 laden und je Region und Mitglied aufbereiten, damit
mehrtägige Prognosen eine Streuung erhalten.
<<<
QUELLE: ARCHITEKTUR.md 5.6
RELATIONS:
- TYPE: Parent
  VALUE: STK-001
- TYPE: Parent
  VALUE: STK-002

[REQUIREMENT]
UID: SYSR-WX-008
ART: Funktional
STATUS: Umgesetzt
NACHWEIS: Demonstration
TITLE: Wetter für das Verbundnetz
STATEMENT: >>>
Das System muss GFS 0,5° für Europa laden und je Gebotszone aufbereiten, damit Einflüsse der
Nachbarländer in die Prognose eingehen.
<<<
QUELLE: ARCHITEKTUR.md 5.7
RELATIONS:
- TYPE: Parent
  VALUE: STK-001
- TYPE: Parent
  VALUE: STK-004

[REQUIREMENT]
UID: SYSR-WX-009
ART: Funktional
STATUS: Geplant
TITLE: Weitere Wettermodelle
STATEMENT: >>>
Das System soll weitere freie Wettermodelle (ECMWF IFS/AIFS Open Data, DWD ICON, GEM) einbinden.
<<<
QUELLE: SPECIFICATION.md 4; ARCHITEKTUR.md 3.1
RELATIONS:
- TYPE: Parent
  VALUE: STK-004

[[/SECTION]]

[[SECTION]]
TITLE: Energie-, Markt- und Anlagendaten

[REQUIREMENT]
UID: SYSR-EN-001
ART: Funktional
STATUS: Umgesetzt
NACHWEIS: Test, Demonstration
TITLE: Energie- und Marktdaten abgleichen
STATEMENT: >>>
Das System muss Preise, Last, Erzeugung je Träger und Prognosen der Netzbetreiber für DE-LU
mindestens alle 15 min abgleichen, rückwirkend korrigierte Werte übernehmen und die Historie
schrittweise nachladen.
<<<
QUELLE: SPECIFICATION.md 5, 6.2
RELATIONS:
- TYPE: Parent
  VALUE: STK-001
- TYPE: Parent
  VALUE: STK-002
- TYPE: Parent
  VALUE: STK-005

[REQUIREMENT]
UID: SYSR-EN-002
ART: Funktional
STATUS: Umgesetzt
NACHWEIS: Test
TITLE: Mehrere Quellen je Reihe mit Rangfolge
STATEMENT: >>>
Das System muss je Reihe alle freigegebenen Quellen getrennt speichern, gegeneinander prüfen und
für das Lernen die Quelle mit dem kleinsten Rang verwenden. SMARD hat Rang 1.
<<<
QUELLE: SPECIFICATION.md 6.2; Projektentscheidung SMARD Rang 1
RELATIONS:
- TYPE: Parent
  VALUE: STK-004

[REQUIREMENT]
UID: SYSR-EN-003
ART: Qualität
STATUS: Umgesetzt
NACHWEIS: Test
TITLE: Veröffentlichungszeitpunkt je Wert
STATEMENT: >>>
Jeder Energiewert muss den Zeitpunkt tragen, ab dem er bekannt war. Training und Backtest dürfen
nur Werte verwenden, die zum Prognosezeitpunkt bekannt waren.
<<<
QUELLE: SPECIFICATION.md 2, 6.2
RELATIONS:
- TYPE: Parent
  VALUE: STK-014

[REQUIREMENT]
UID: SYSR-EN-004
ART: Funktional
STATUS: Umgesetzt
NACHWEIS: Test
TITLE: Anlagenbestand aus dem MaStR
STATEMENT: >>>
Das System muss den MaStR-Gesamtexport quartalsweise sichern, die installierte Leistung je
Gebietscluster und Tag rekonstruieren und Cluster versioniert höchstens jährlich neu bilden.
<<<
QUELLE: SPECIFICATION.md 6.2; ARCHITEKTUR.md 7.5
RELATIONS:
- TYPE: Parent
  VALUE: STK-010

[REQUIREMENT]
UID: SYSR-EN-005
ART: Funktional
STATUS: Umgesetzt
NACHWEIS: Test
TITLE: Brennstoff- und Speicherdaten
STATEMENT: >>>
Das System muss freie Reihen zu Brennstoffpreisen, Gasspeichern und Energieprognosen (Eurostat,
GIE AGSI+, EIA STEO) einbeziehen, soweit sie das Preisniveau erklären.
<<<
QUELLE: ARCHITEKTUR.md 7.11.1; docs/analysen/preisniveau-schaetzung
RELATIONS:
- TYPE: Parent
  VALUE: STK-001
- TYPE: Parent
  VALUE: STK-004

[REQUIREMENT]
UID: SYSR-EN-006
ART: Randbedingung
STATUS: Umgesetzt
NACHWEIS: Test, Inspektion
TITLE: Freigabe unfreier Quellen
STATEMENT: >>>
Jede Quelle muss als frei oder unfrei geführt werden. Unfreie Quellen laufen nur, wenn die
zugehörige Variable ``PDB_ALLOW_*`` gesetzt ist, Vorgabe ist aus. Daten unfreier Quellen dürfen
nicht in Modelle oder Daten eingehen, die veröffentlicht werden.
<<<
QUELLE: ARCHITEKTUR.md 7.11.1
RELATIONS:
- TYPE: Parent
  VALUE: STK-034
- TYPE: Parent
  VALUE: STK-003

[[/SECTION]]

[[SECTION]]
TITLE: Prognose und Training

[REQUIREMENT]
UID: SYSR-PR-001
ART: Funktional
STATUS: Teilweise
NACHWEIS: Test, Demonstration
TITLE: Last und Preis als Quantile
STATEMENT: >>>
Das System muss Netzlast DE und Day-Ahead-Preis DE-LU in 15-min-Auflösung als Quantile
prognostizieren, den Preis mindestens für D+1 und als Szenario bis D+14.
<<<
QUELLE: SPECIFICATION.md 1, 6.3; ARCHITEKTUR.md 7.1, 7.3
RELATIONS:
- TYPE: Parent
  VALUE: STK-001
- TYPE: Parent
  VALUE: STK-002

[REQUIREMENT]
UID: SYSR-PR-002
ART: Funktional
STATUS: Umgesetzt
NACHWEIS: Demonstration
TITLE: Prognose nach jedem neuen Lauf
STATEMENT: >>>
Das System muss nach jedem neuen vollständigen Wetterlauf mit allen aktiven Modellversionen eine
Prognose erstellen und ablegen. Neu registrierte Modelle müssen sofort rückwirkend Prognosen für
den Vergleich erhalten.
<<<
QUELLE: compose.yaml (ml-predict); ARCHITEKTUR.md 7.4
RELATIONS:
- TYPE: Parent
  VALUE: STK-001
- TYPE: Parent
  VALUE: STK-014

[REQUIREMENT]
UID: SYSR-PR-003
ART: Qualität
STATUS: Umgesetzt
NACHWEIS: Test
TITLE: Kein Vorgriff auf Zukunftswissen
STATEMENT: >>>
In eine Prognose dürfen nur Wetterläufe und Messwerte eingehen, die zum Ausgabezeitpunkt
verfügbar waren (``run_time`` + Verzug ≤ ``issue_time``).
<<<
QUELLE: SPECIFICATION.md 6.3; ARCHITEKTUR.md 7.4
RELATIONS:
- TYPE: Parent
  VALUE: STK-014

[REQUIREMENT]
UID: SYSR-PR-004
ART: Funktional
STATUS: Umgesetzt
NACHWEIS: Test, Analyse
TITLE: Backtest und Gütemaße
STATEMENT: >>>
Das System muss jedes Modell rollierend zurückrechnen und Gütemaße je Ziel, Quantil und Vorlauf
ausgeben.
<<<
QUELLE: docs/BACKTEST.md
RELATIONS:
- TYPE: Parent
  VALUE: STK-014

[REQUIREMENT]
UID: SYSR-TR-001
ART: Funktional
STATUS: Umgesetzt
NACHWEIS: Demonstration
TITLE: Training als portabler Job
STATEMENT: >>>
Training muss als Container-Job auf CPU, lokaler oder gemieteter GPU laufen können. Ein Job darf
nur einen Trainings-Snapshot brauchen, keinen Zugang ins Heimnetz.
<<<
QUELLE: SPECIFICATION.md 6.5; ARCHITEKTUR.md 7.7
RELATIONS:
- TYPE: Parent
  VALUE: STK-006

[REQUIREMENT]
UID: SYSR-TR-002
ART: Funktional
STATUS: Teilweise
NACHWEIS: Demonstration
TITLE: Champion und Challenger
STATEMENT: >>>
Ein neues Modell darf das Produktionsmodell erst nach einem Vergleich (Champion/Challenger)
ersetzen. Mehrere Modellversionen laufen parallel, ihre Streuung wird als Unsicherheitsmaß
gespeichert.
<<<
QUELLE: SPECIFICATION.md 6.3, 6.5; docs/PROGNOSEMODELLE.md
RELATIONS:
- TYPE: Parent
  VALUE: STK-014

[REQUIREMENT]
UID: SYSR-TR-003
ART: Funktional
STATUS: Geplant
TITLE: Wöchentliches Neutraining
STATEMENT: >>>
Das System soll das Produktionsmodell wöchentlich automatisch nachtrainieren, sobald mindestens
drei Jahre GFS-Historie vorliegen. Vorher wird es nicht eingerichtet.
<<<
QUELLE: Projektentscheidung 2026-10-24
RELATIONS:
- TYPE: Parent
  VALUE: STK-015

[REQUIREMENT]
UID: SYSR-PR-005
ART: Funktional
STATUS: Geplant
TITLE: API für eigene Anlagen
STATEMENT: >>>
Das System muss eine HTTP-API bieten, über die Nutzer eigene PV-, Wind- und Wasserkraftanlagen
anlegen, Messwerte und Abschaltregeln hochladen, kalibrieren und Prognosen mit Quantilen abrufen.
<<<
QUELLE: SPECIFICATION.md 6.4; ARCHITEKTUR.md 7.6
RELATIONS:
- TYPE: Parent
  VALUE: STK-011
- TYPE: Parent
  VALUE: STK-036

[REQUIREMENT]
UID: SYSR-PR-006
ART: Funktional
STATUS: Vorgemerkt
TITLE: Wärme, Kälte und Wärmepumpen
STATEMENT: >>>
Das System soll Wärme- und Kältebedarf, den Strombedarf von Wärmepumpen und deren optimalen
Betrieb für Folgetag, 24 h und 96 h vorhersagen. Die nötigen Wettervariablen werden bereits
gesammelt.
<<<
QUELLE: SPECIFICATION.md 6.6; ARCHITEKTUR.md 7.8
RELATIONS:
- TYPE: Parent
  VALUE: STK-012

[[/SECTION]]

[[SECTION]]
TITLE: Veröffentlichung und Austausch

[REQUIREMENT]
UID: SYSR-PUB-001
ART: Funktional
STATUS: Umgesetzt
NACHWEIS: Demonstration
TITLE: Silber über GHCR austauschen
STATEMENT: >>>
Das System muss Silber als ORAS-Artefakte in GHCR veröffentlichen und daraus importieren können.
Der Import muss den Inhalt über Hashes prüfen.
<<<
QUELLE: ARCHITEKTUR.md 5.5
RELATIONS:
- TYPE: Parent
  VALUE: STK-016
- TYPE: Parent
  VALUE: STK-003

[REQUIREMENT]
UID: SYSR-PUB-002
ART: Funktional
STATUS: Umgesetzt
NACHWEIS: Test, Demonstration
TITLE: Wetterhistorie in GitHub Actions bauen
STATEMENT: >>>
Die Silber-Historie für GFS und GEFS muss in GitHub-Actions-Runnern gebaut werden können, ohne
die Bandbreite der VM zu belasten.
<<<
QUELLE: ARCHITEKTUR.md 5.5, 5.6
RELATIONS:
- TYPE: Parent
  VALUE: STK-015
- TYPE: Parent
  VALUE: STK-038

[REQUIREMENT]
UID: SYSR-PUB-003
ART: Funktional
STATUS: Teilweise
NACHWEIS: Inspektion
TITLE: Modelle mit Modellkarte veröffentlichen
STATEMENT: >>>
Das System muss trainierte Modelle als versionierte Artefakte mit Modellkarte veröffentlichen.
Die Modellkarte nennt alle Quellen mit Lizenz und Quellenvermerk. Mit dem Modell wird keine
Datenreihe ausgeliefert, die nicht frei weitergegeben werden darf.
<<<
QUELLE: ARCHITEKTUR.md 7.11
RELATIONS:
- TYPE: Parent
  VALUE: STK-003
- TYPE: Parent
  VALUE: STK-035

[REQUIREMENT]
UID: SYSR-PUB-004
ART: Funktional
STATUS: Umgesetzt
NACHWEIS: Test, Demonstration
TITLE: Schlanker Prognose-Stack
STATEMENT: >>>
Es muss einen eigenständigen Prognose-Stack geben, der ein Modellpaket lädt, die Eingänge direkt
bei freien Quellen abruft und Prognosen als Dateien und über HTTP ausgibt.
<<<
QUELLE: predict/README.md
RELATIONS:
- TYPE: Parent
  VALUE: STK-013

[REQUIREMENT]
UID: SYSR-PUB-005
ART: Funktional
STATUS: Umgesetzt
NACHWEIS: Inspektion
TITLE: Zugangsdoku je Quelle
STATEMENT: >>>
Für jede Quelle muss dokumentiert sein, welche Zugänge, Schlüssel und Lizenzen sie verlangt und
welche Variable sie freischaltet.
<<<
QUELLE: docs/DATENQUELLEN-ZUGANG.md
RELATIONS:
- TYPE: Parent
  VALUE: STK-019

[REQUIREMENT]
UID: SYSR-PUB-006
ART: Funktional
STATUS: Umgesetzt
NACHWEIS: Test, Demonstration
TITLE: Öffentliche Prognose
STATEMENT: >>>
Das System muss die aktuelle Prognose (Preis und Last, D+0 bis D+15) mindestens täglich
ohne Anmeldung öffentlich zugänglich machen, unter einer gleichbleibenden Adresse und mit den
Quellenvermerken. Ältere Stände sollen eine Zeit lang zum Vergleich erreichbar bleiben. Wie und
wo veröffentlicht wird, ist austauschbar und nicht Teil dieser Anforderung.
<<<
RATIONALE: >>>
Heute als Grafana-Snapshot auf snapshots.raintank.io mit Kurzlink go.the78mole.de/predb
(SWR-WXX-050, SWR-WXX-051). Die Art der Veröffentlichung kann sich noch ändern.
<<<
RELATIONS:
- TYPE: Parent
  VALUE: STK-003
- TYPE: Parent
  VALUE: STK-014

[[/SECTION]]

[[SECTION]]
TITLE: Betrieb

[REQUIREMENT]
UID: SYSR-OPS-001
ART: Qualität
STATUS: Umgesetzt
NACHWEIS: Test
TITLE: Wiederanlauf und Idempotenz
STATEMENT: >>>
Jeder Dienst muss nach einem Abbruch ohne Eingriff weiterlaufen und bereits erledigte Arbeit nicht
erneut ausführen. Der Zustand liegt in der Datenbank bzw. in Manifesten, nicht im Prozess.
<<<
QUELLE: SPECIFICATION.md 7
RELATIONS:
- TYPE: Parent
  VALUE: STK-017

[REQUIREMENT]
UID: SYSR-OPS-002
ART: Funktional
STATUS: Umgesetzt
NACHWEIS: Demonstration
TITLE: Automatisches Ausrollen
STATEMENT: >>>
Nach jeder grünen CI auf ``main`` muss die VM den neuen Stand selbst ausrollen. Schlägt ein
Schritt fehl, bleibt der alte Stand in Betrieb.
<<<
QUELLE: README.md (Auto-Update)
RELATIONS:
- TYPE: Parent
  VALUE: STK-017

[REQUIREMENT]
UID: SYSR-OPS-003
ART: Funktional
STATUS: Umgesetzt
NACHWEIS: Demonstration
TITLE: Dashboards
STATEMENT: >>>
Das System muss Prognosen mit Istwerten und Vortagesvergleich, den Datenbestand je Stufe und
Monat sowie den Zustand von Diensten und Ressourcen in Dashboards zeigen.
<<<
QUELLE: ARCHITEKTUR.md 7.10, 10
RELATIONS:
- TYPE: Parent
  VALUE: STK-014
- TYPE: Parent
  VALUE: STK-017

[REQUIREMENT]
UID: SYSR-OPS-004
ART: Funktional
STATUS: Teilweise
NACHWEIS: Demonstration
TITLE: Alarme per E-Mail
STATEMENT: >>>
Das System muss den Betreiber per E-Mail alarmieren, wenn sich das Format einer Quelle ändert,
ein Abruf seit 24 h scheitert, eine Reihe veraltet, kein vollständiger GFS-Lauf seit 12 h
vorliegt oder ein Datenträger zu 90 % belegt ist.
<<<
QUELLE: ARCHITEKTUR.md 10
RELATIONS:
- TYPE: Parent
  VALUE: STK-017

[REQUIREMENT]
UID: SYSR-OPS-005
ART: Qualität
STATUS: Umgesetzt
NACHWEIS: Inspektion
TITLE: Strukturierte Protokolle und Metriken
STATEMENT: >>>
Alle Dienste müssen strukturierte JSON-Protokolle schreiben. Ressourcen und Container müssen als
Metriken erfasst werden.
<<<
QUELLE: SPECIFICATION.md 7; compose.yaml (prometheus, node-exporter, cadvisor)
RELATIONS:
- TYPE: Parent
  VALUE: STK-017

[REQUIREMENT]
UID: SYSR-OPS-006
ART: Funktional
STATUS: Geplant
TITLE: Sicherung
STATEMENT: >>>
Datenbank und nicht wiederbeschaffbare Objekte müssen regelmäßig gesichert werden.
<<<
QUELLE: SPECIFICATION.md 3.1 (Bucket backups)
RELATIONS:
- TYPE: Parent
  VALUE: STK-017

[REQUIREMENT]
UID: SYSR-OPS-007
ART: Funktional
STATUS: Umgesetzt
NACHWEIS: Inspektion
TITLE: Analyse-Jobs
STATEMENT: >>>
Analysen müssen als Job mit Konfiguration, Code und Ergebnisordner im Repo liegen, mit Commit und
Image protokolliert werden und als PDF am Release hängen.
<<<
QUELLE: ARCHITEKTUR.md 7.9
RELATIONS:
- TYPE: Parent
  VALUE: STK-018

[[/SECTION]]

[[SECTION]]
TITLE: Sicherheit der Lieferkette

[TEXT]
STATEMENT: >>>
Die Anforderungen dieses Abschnitts orientieren sich an den Prüfungen von OpenSSF Scorecard
(Workflow ``scorecard.yml``, Ergebnis auf scorecard.dev). Prüfungen, die zu einem Projekt mit
einer Person nicht passen, sind bewusst nicht als Anforderung aufgenommen, siehe SYSR-SEC-008.
<<<

[REQUIREMENT]
UID: SYSR-SEC-001
ART: Qualität
STATUS: Umgesetzt
NACHWEIS: Inspektion
TITLE: Kein fremder Code mit Schreibrechten
STATEMENT: >>>
Workflows, die mit Schreibrechten oder Geheimnissen laufen (``workflow_run``,
``pull_request_target``, ``schedule``, ``workflow_dispatch``), dürfen nur Commits ausführen, die
bereits auf ``main`` liegen. Code aus Pull Requests, insbesondere aus Forks, darf nur in Workflows
mit Leserechten und ohne Geheimnisse laufen.
<<<
RATIONALE: >>>
Ein ``workflow_run`` nach einem Fork-PR liefe sonst mit den Rechten des Repos. Die Bedingung
``event == 'push'`` allein reicht nicht als einzige Sicherung, weil der Filter ``branches`` nur
den Branchnamen prüft.
<<<
QUELLE: OpenSSF Scorecard Dangerous-Workflow; scripts/main-commit-auschecken.sh
RELATIONS:
- TYPE: Parent
  VALUE: STK-039

[REQUIREMENT]
UID: SYSR-SEC-002
ART: Qualität
STATUS: Umgesetzt
NACHWEIS: Inspektion
TITLE: Minimale Token-Rechte
STATEMENT: >>>
Jeder Workflow muss auf oberster Ebene höchstens Leserechte vergeben. Schreibrechte
(``contents``, ``packages``, ``pages``, ``id-token``, ``security-events``) dürfen nur Jobs
erhalten, die sie brauchen.
<<<
RATIONALE: >>>
Alle Workflows vergeben oben nur ``contents: read`` (``scorecard.yml``: ``read-all``);
Schreibrechte stehen nur an den Jobs, die schreiben.
<<<
QUELLE: OpenSSF Scorecard Token-Permissions
RELATIONS:
- TYPE: Parent
  VALUE: STK-039

[REQUIREMENT]
UID: SYSR-SEC-003
ART: Qualität
STATUS: Umgesetzt
NACHWEIS: Inspektion
TITLE: Abhängigkeiten fest gepinnt
STATEMENT: >>>
Abhängigkeiten müssen unveränderlich festgelegt sein: Python-Pakete über ``uv.lock`` mit Hashes,
GitHub Actions über den vollständigen Commit-Hash, Container-Basisimages über den Digest.
Renovate muss diese Festlegungen aktuell halten.
<<<
RATIONALE: >>>
Actions stehen als ``@<sha> # vX.Y.Z``, die Images in ``docker/Dockerfile`` und
``predict/Dockerfile`` als ``Tag@sha256:…``; Renovate (``helpers:pinGitHubActionDigests``,
``pinDigests`` für Dockerfiles) aktualisiert beides in den Minor-/Patch-Gruppen. Images in den
Compose-Dateien laufen weiter über Tags, sie sind keine Basisimages eines Builds.
<<<
QUELLE: OpenSSF Scorecard Pinned-Dependencies; renovate.json
RELATIONS:
- TYPE: Parent
  VALUE: STK-039
- TYPE: Parent
  VALUE: STK-030

[REQUIREMENT]
UID: SYSR-SEC-004
ART: Qualität
STATUS: Umgesetzt
NACHWEIS: Inspektion
TITLE: Statische Sicherheitsanalyse
STATEMENT: >>>
Jede Änderung an ``main`` und jeder Pull Request muss mit einer statischen Sicherheitsanalyse
(CodeQL für Python und Workflows) geprüft werden. Funde erscheinen im Code Scanning.
<<<
QUELLE: OpenSSF Scorecard SAST; CodeQL Default Setup (Repository-Einstellung)
RELATIONS:
- TYPE: Parent
  VALUE: STK-039

[REQUIREMENT]
UID: SYSR-SEC-005
ART: Qualität
STATUS: Teilweise
NACHWEIS: Inspektion
TITLE: Herkunftsnachweis für Veröffentlichungen
STATEMENT: >>>
Container-Images, Modellartefakte und Silber-Artefakte auf GHCR sowie Release-Anhänge müssen
einen prüfbaren Herkunftsnachweis tragen (Build-Provenance bzw. Signatur), der sie einem Commit
und Workflow-Lauf dieses Repositorys zuordnet.
<<<
RATIONALE: >>>
Umgesetzt für die Images ``predictiondb`` und ``predictiondb-predict`` (Attestation per
``actions/attest-build-provenance`` an GHCR), für die Analyse-PDFs der Releases (Bundle
``analysen-pdf.intoto.jsonl`` als Release-Anhang) und für das Quellcode-Archiv jedes Releases
(``PredictionDB-vX.Y.Z.tar.gz`` mit Bundle ``quellcode.intoto.jsonl``). Offen: Modell- und
Silber-Artefakte auf GHCR.
<<<
QUELLE: OpenSSF Scorecard Signed-Releases
RELATIONS:
- TYPE: Parent
  VALUE: STK-039
- TYPE: Parent
  VALUE: STK-016

[REQUIREMENT]
UID: SYSR-SEC-006
ART: Funktional
STATUS: Umgesetzt
NACHWEIS: Inspektion
TITLE: Lücken vertraulich melden, Geheimnisse schützen
STATEMENT: >>>
Das Repository muss eine Sicherheitsrichtlinie mit vertraulichem Meldeweg (Private Vulnerability
Reporting) haben. Secret Scanning mit Push Protection muss Geheimnisse in Commits erkennen und
abweisen.
<<<
QUELLE: SECURITY.md; OpenSSF Scorecard Security-Policy; Repository-Einstellungen
RELATIONS:
- TYPE: Parent
  VALUE: STK-039

[REQUIREMENT]
UID: SYSR-SEC-007
ART: Qualität
STATUS: Umgesetzt
NACHWEIS: Inspektion
TITLE: Schutz von main
STATEMENT: >>>
Änderungen an ``main`` dürfen nur über Pull Requests mit grüner CI möglich sein. Force-Push und
Löschen von ``main`` müssen gesperrt sein.
<<<
RATIONALE: >>>
Umgesetzt als Ruleset „main schützen“ (seit 2026-11-01): PR Pflicht, CI-Jobs Lint und Typen,
Unit-Tests sowie Image und Compose-Stack müssen grün sein, kein Force-Push, kein Löschen;
Admins dürfen nur im PR übersteuern. Eine Freigabe durch eine zweite Person ist nicht
verlangt, siehe SYSR-SEC-008.
<<<
QUELLE: OpenSSF Scorecard Branch-Protection
RELATIONS:
- TYPE: Parent
  VALUE: STK-039

[REQUIREMENT]
UID: SYSR-SEC-008
ART: Qualität
STATUS: Umgesetzt
NACHWEIS: Analyse
TITLE: Regelmäßige Bewertung der Sicherheitspraxis
STATEMENT: >>>
Die Sicherheitspraxis des Repositorys muss bei jeder Änderung an ``main`` und wöchentlich mit
OpenSSF Scorecard bewertet und das Ergebnis öffentlich gemacht werden (Badge im README und auf der
Projektseite).
<<<
RATIONALE: >>>
Bewusst nicht verfolgt: Code-Review (keine zweite Person zur Freigabe), Contributors (Projekt
einer Person) und das OpenSSF-Best-Practices-Badge (Selbstauskunft ohne Nutzen für die
Anwender).
<<<
QUELLE: .github/workflows/scorecard.yml
RELATIONS:
- TYPE: Parent
  VALUE: STK-039

[REQUIREMENT]
UID: SYSR-SEC-009
ART: Qualität
STATUS: Teilweise
NACHWEIS: Test
TITLE: Fuzzing externer Eingaben
STATEMENT: >>>
Code, der Daten von außen parst, muss mit zufällig erzeugten und verfälschten Eingaben geprüft
werden: mindestens ``.idx``-Inventare, GRIB-Kopfdaten und Byte-Bereiche in gribkit, die Antworten
der Energiequellen (JSON, XML) und die Manifeste der GHCR-Artefakte. Ungültige Eingaben dürfen nur
zu den vorgesehenen Fehlern führen, nie zu Abstürzen, Endlosschleifen oder falsch übernommenen
Daten. Property-Tests laufen mit den Unit-Tests bei jedem Pull Request, ein Fuzzer zusätzlich
regelmäßig.
<<<
RATIONALE: >>>
Die Eingaben stammen von NOAA, GDEX, den Energiequellen und über GHCR von anderen Instanzen und
sind damit nicht vertrauenswürdig. Property-Tests mit Hypothesis, Fuzzer mit Atheris
(``fuzz/``, Workflow ``fuzz.yml``), den auch OpenSSF Scorecard (Prüfung Fuzzing) erkennt.
Umgesetzt für gribkit, das seit 2026-11-01 als externes Paket (SYSA-EXT-GRIBKIT) im eigenen
Repository the78mole/gribkit gepflegt und dort gefuzzt wird, für die GHCR-Artefakte
(SWR-WXX-060) und für ENTSO-E (SWR-ENI-033); offen sind die übrigen Energiequellen.
<<<
QUELLE: OpenSSF Scorecard Fuzzing; Entscheidung 2026-11-01
RELATIONS:
- TYPE: Parent
  VALUE: STK-039
- TYPE: Parent
  VALUE: STK-016

[[/SECTION]]

[[SECTION]]
TITLE: Qualität und Randbedingungen

[REQUIREMENT]
UID: SYSR-QA-001
ART: Qualität
STATUS: Umgesetzt
NACHWEIS: Analyse
TITLE: Ressourcenrahmen der VM
STATEMENT: >>>
Der Stack muss in einer VM mit 6–8 vCPU, 24–32 GB RAM und 500 GB Datenplatte laufen. Wetter
soll in der Größenordnung von 15 GB je Jahr und Modell belegen.
<<<
QUELLE: SPECIFICATION.md 7; ARCHITEKTUR.md 5.4, 8.1
RELATIONS:
- TYPE: Parent
  VALUE: STK-006
- TYPE: Parent
  VALUE: STK-031

[REQUIREMENT]
UID: SYSR-QA-002
ART: Qualität
STATUS: Umgesetzt
NACHWEIS: Inspektion
TITLE: Portabilität in die Cloud
STATEMENT: >>>
Das System darf nur S3-API, Postgres-Protokoll und Konfiguration über die Umgebung voraussetzen,
damit ein Umzug in die Cloud reine Konfiguration ist.
<<<
QUELLE: SPECIFICATION.md 7; ARCHITEKTUR.md 9
RELATIONS:
- TYPE: Parent
  VALUE: STK-006
- TYPE: Parent
  VALUE: STK-032

[REQUIREMENT]
UID: SYSR-QA-003
ART: Randbedingung
STATUS: Umgesetzt
NACHWEIS: Inspektion
TITLE: Konfiguration und Geheimnisse
STATEMENT: >>>
Die Konfiguration muss über Variablen mit Präfix ``PDB_`` in der ``.env`` erfolgen. Geheimnisse
(Passwörter, Token) kommen aus OpenBao in die ``.env``; Hosts, URLs und Adressen sind normale
Werte.
<<<
QUELLE: ARCHITEKTUR.md 8.3; Projektentscheidung 2026-10-24
RELATIONS:
- TYPE: Parent
  VALUE: STK-037

[REQUIREMENT]
UID: SYSR-QA-004
ART: Randbedingung
STATUS: Teilweise
NACHWEIS: Inspektion
TITLE: Quellenvermerke
STATEMENT: >>>
Jede Quelle muss ihre Lizenz in ``meta.source`` führen. Dashboards, API-Antworten und
veröffentlichte Artefakte müssen die geforderten Quellenvermerke tragen.
<<<
QUELLE: SPECIFICATION.md 7; ARCHITEKTUR.md 10
RELATIONS:
- TYPE: Parent
  VALUE: STK-035

[REQUIREMENT]
UID: SYSR-QA-005
ART: Randbedingung
STATUS: Geplant
NACHWEIS: Test
TITLE: Datenschutz eigener Anlagen
STATEMENT: >>>
Standort und Messwerte eigener Anlagen dürfen das System nicht verlassen, nicht mit dem MaStR
verknüpft werden und müssen mit der Anlage vollständig gelöscht werden.
<<<
QUELLE: SPECIFICATION.md 7
RELATIONS:
- TYPE: Parent
  VALUE: STK-036

[REQUIREMENT]
UID: SYSR-QA-006
ART: Qualität
STATUS: Umgesetzt
NACHWEIS: Inspektion
TITLE: Prüfungen vor dem Zusammenführen
STATEMENT: >>>
Jede Änderung muss vor dem Zusammenführen Lint, Typprüfung, Unit-Tests, Integrationstests gegen
den Compose-Stack und die Prüfung der Anforderungen bestehen.
<<<
QUELLE: .github/workflows/ci.yml
RELATIONS:
- TYPE: Parent
  VALUE: STK-030
- TYPE: Parent
  VALUE: STK-017

[REQUIREMENT]
UID: SYSR-QA-007
ART: Randbedingung
STATUS: Umgesetzt
NACHWEIS: Inspektion
TITLE: Softwareelemente als Python-Pakete
STATEMENT: >>>
Jedes Softwareelement muss als eigenes, reguläres Python-Paket im uv-Workspace vorliegen
(src-Layout mit ``__init__.py`` und ``py.typed``). Der Paket-Docstring muss den Zweck des
Elements in einem Satz nennen und auf sein Softwareelement verweisen. Die Version steht nur in
``pyproject.toml``.
<<<
RATIONALE: >>>
Reguläre Pakete statt Namespace-Paketen machen den Paketeinstieg eindeutig und rückverfolgbar;
``py.typed`` lässt mypy die Typen auch über Paketgrenzen prüfen. Eine zweite Versionsangabe im
Code veraltet unbemerkt.
<<<
QUELLE: reqs/README.md (Verweise aus Code und Tests); reqs/pruefen.py
RELATIONS:
- TYPE: Parent
  VALUE: STK-030

[[/SECTION]]
